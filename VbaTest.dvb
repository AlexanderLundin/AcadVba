Attribute VB_Name = "TestModule1"
Option Explicit
Option Private Module

'@TestModule
'@Folder("Tests")

Private Assert As Object
Private Fakes As Object

'@ModuleInitialize
Private Sub ModuleInitialize()
    'this method runs once per module.
    Set Assert = CreateObject("Rubberduck.AssertClass")
    Set Fakes = CreateObject("Rubberduck.FakesProvider")
    ' Set SDI to 1, because Rubber duck has issues opening new .dwgs
    ' when Acad is not in SDI mode 1
    ThisDrawing.SetVariable "SDI", 1
End Sub

'@ModuleCleanup
Private Sub ModuleCleanup()
    'this method runs once per module.
    Set Assert = Nothing
    Set Fakes = Nothing
End Sub

'@TestInitialize
Private Sub TestInitialize()
    'This method runs before every test in the module..
End Sub

'@TestCleanup
Private Sub TestCleanup()
    'this method runs after every test in the module.
End Sub

'@TestMethod
Public Sub TestGetActiveLayerName()
    Dim layerName As String
    Dim layer As AcadLayer
    Set layer = ThisDrawing.ActiveLayer
    layerName = layer.Name
    Assert.isTrue True
End Sub

'@TestMethod
Public Sub TestInsertDrawingAsBlockAndDelete_ShouldPass()
    Dim appAcad As AcadApplication
    Set appAcad = GetAcad
    
    
    Dim blockName As String
    blockName = "testBlock"
    Dim blockObject As AcadBlock
    Set blockObject = ThisDrawing.Blocks.Add(TestUtilities.ConstantInsertionPointZeroZeroZero(), blockName)
    
    blockObject.AddAttribute 5#, acAttributeModeNormal, "promptString", TestUtilities.ConstantInsertionPointZeroZeroZero(), "tag", "value"
    blockObject.AddLine TestUtilities.ConstantInsertionPointZeroZeroZero(), TestUtilities.ConstantInsertionPointOneOneOne()
    
    
    Dim blockReference As AcadBlockReference
    Set blockReference = ThisDrawing.ModelSpace.InsertBlock(ConstantInsertionPointOneOneOne(), blockName, 1#, 1#, 1#, 0#)
    
    
    Dim blockDrawingPath As String
    blockDrawingPath = SaveCurrentDwgToTempFolder(ThisDrawing)
    
    Dim newDoc As AcadDocument
    ' use this method to open new document is SDI = 1
    Set newDoc = ThisDrawing.New("acad.dwt")
    
    InsertDrawingThenDelete newDoc, blockDrawingPath
    Set blockReference = newDoc.ModelSpace.InsertBlock(ConstantInsertionPointOneOneOne(), blockName, 1#, 1#, 1#, 0#)
    
    Assert.isTrue True
End Sub


Public Function IsAutoCADQuiescent(appAcad As AcadApplication) As Integer
    On Error GoTo ErrorHandler
    Dim State As AcadState
    IsAutoCADQuiescent = -1
    Set State = appAcad.GetAcadState
    DoEvents
    While (State.IsQuiescent <> True)
        DoEvents
        Set State = appAcad.GetAcadState
    Wend
    Set State = Nothing
    IsAutoCADQuiescent = 0
    Exit Function
ErrorHandler:
    MsgBox "Error: " & Err.Number & " :: " & Err.Description
End Function

Attribute VB_Name = "TestUtilities"

Public Sub AcadExportAllModules()
    Dim appAcad As AcadApplication
    Set appAcad = GetAcad()
    AcadExportVbaProjects appAcad
    
End Sub

Sub AcadExportVbaProjects(appAcad As AcadApplication)
    Dim objIDE As Object
    Dim projects As Object
    Dim exportFolder As String
    Dim project As Object
    
    Set objIDE = AcadApplication.VBE
    Set projects = objIDE.VBProjects
    
    For Each project In projects
        exportFolder = GetFolderName(project.fileName)
        For Each Module In project.VBComponents
            Module.Export (exportFolder & "\" & Module.Name & ".bas")
        Next Module
    Next project

End Sub




' Section AutoCAD










Public Function GetAcad() As AcadApplication
    Dim appAcad As AcadApplication
    Set appAcad = GetObject(, "AutoCAD.Application")
    Set GetAcad = appAcad
End Function

Public Sub InsertDrawingThenDelete(doc As AcadDocument, drawingToInsert As String)
    Dim XYZScale As Double
    Dim rotation As Double
    XYZScale = 1#
    rotation = 0#
    InsertDrawingAsBlockThenDelete doc, ConstantInsertionPointZeroZeroZero(), drawingToInsert, XYZScale, rotation
End Sub

Public Function SaveCurrentDwgToTempFolder(doc As AcadDocument) As String
    Dim fileName As String
    fileName = GetNewDwgFileInTempFolder()
    doc.SaveAs (fileName)
    SaveCurrentDwgToTempFolder = fileName
End Function

Public Sub InsertDrawingAsBlockThenDelete(doc As AcadDocument, insertionPt As Variant, drawingToInsert As String, XYZScale As Double, rotation As Double)
    Dim objBlockRef As AcadBlockReference
    On Error Resume Next
        Set objBlockRef = doc.ModelSpace.InsertBlock(insertionPt, drawingToInsert, XYZScale, _
        XYZScale, XYZScale, rotation)
    If Err Then
        MsgBox "Unable to insert this block. " + Err.Description
    End If
    objBlockRef.Delete
End Sub








' Section Constants










Public Function ConstantInsertionPointZeroZeroZero() As Variant
    Dim insertionPointZeroZeroZero(0 To 2) As Double
    insertionPointZeroZeroZero(0) = 0
    insertionPointZeroZeroZero(1) = 0
    insertionPointZeroZeroZero(2) = 0
    ConstantInsertionPointZeroZeroZero = insertionPointZeroZeroZero
End Function

Public Function ConstantInsertionPointOneOneOne() As Variant
    Dim insertionPointOneOneOne(0 To 2) As Double
    insertionPointOneOneOne(0) = 1
    insertionPointOneOneOne(1) = 1
    insertionPointOneOneOne(2) = 1
    ConstantInsertionPointOneOneOne = insertionPointOneOneOne
End Function









' Section Files








'FSO, Needs reference to Microsoft Visual Basic for Applications Extensibility 5.3 or greater
Sub FSOGetFileName(fileName As String)
    Dim FSO As New FileSystemObject
    Set FSO = CreateObject("Scripting.FileSystemObject")
    'Get File Name no Extension
    FSOGetFileName = Left(fileName, InStr(fileName, ".") - 1)
End Sub

Public Function GetFolderName(path As String) As String
    Dim directory As String
    directory = Left(path, InStrRev(path, "\") - 1)
    GetFolderName = directory
End Function

Public Function GetNewDwgFileInTempFolder() As String
    Dim fileName As String
    fileName = GetNewFileInTempFolderWithExtension(".dwg")
    GetNewDwgFileInTempFolder = fileName
End Function

Public Function GetNewFileInTempFolderWithExtension(newExtension As String) As String
    Dim fileName As String
    fileName = GetNewFileInTempFolder()
    fileName = Replace(fileName, ".tmp", newExtension)
    GetNewFileInTempFolderWithExtension = fileName
End Function

Public Function GetNewFileInTempFolder() As String
    Dim fileName As String
    fileName = GetTempFileName()
    Dim tempFolder As String
    tempFolder = GetTempFolder()
    Dim newFile As String
    newFile = tempFolder + "\" + fileName
    GetNewFileInTempFolder = newFile
End Function

Public Function GetTempFileName() As String
    Dim FSO As Object
    Set FSO = CreateObject("Scripting.FileSystemObject")
    Dim tempFileName As String
    tempFileName = FSO.GetTempName()
    GetTempFileName = tempFileName
End Function

Public Function GetTempFolder() As String
    Static tempFolderPath As String

    If Len(tempFolderPath) = 0 Then
        Dim fs As Object
        Set fs = CreateObject("Scripting.FileSystemObject")
        
        Const tempFolderFlag = 2
        tempFolderPath = fs.GetSpecialFolder(tempFolderFlag)
    End If
    GetTempFolder = tempFolderPath
End Function

Attribute VB_Name = "ThisDrawing"
Attribute VB_Base = "0{345D3165-3889-4694-AB75-A91A27B217E8}"
Attribute VB_GlobalNameSpace = False
Attribute VB_Creatable = False
Attribute VB_PredeclaredId = True
Attribute VB_Exposed = True
Attribute VB_TemplateDerived = False
Attribute VB_Customizable = True

Public Sub Hello()
    Dim appAcad As AcadApplication
    Set appAcad = GetObject(, "AutoCAD.Application")

    Dim newDoc As AcadDocument
    Set newDoc = ThisDrawing.Application.Documents.Add("acad.dwt")
    'IsAutoCADQuiescent appAcad
    Dim test As String
    test = ""
End Sub
